module ietf-collected-data-manifest {
  yang-version 1.1;
  namespace "urn:ietf:params:xml:ns:yang:ietf-collected-data-manifest";
  prefix data-manifest;

  import ietf-datastores {
    prefix ds;
    reference "RFC 8342: Network Management Datastore Architecture.";
  }

  organization
    "IETF NETCONF (Network Configuration) Working Group";
  contact
    "WG Web:   <https://datatracker.ietf.org/wg/netconf/>
     WG List:  <mailto:netconf@ietf.org>
     Author:   Benoit Claise  <mailto:benoit.claise@huawei.com>
     Author:   Jean Quilbeuf   <mailto:jean.quilbeuf@huawei.com>";
  description
    "This module describes the context of data collection from a
     given network element. The contents of this model must be
     streamed along with the data streamed from the network
     element so that the context of the data collection can
     be retrieved later.

     This module must be completed with
     ietf-collected-data-platform-manifest
     to capture the whole context of a data collection session.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2022 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see the
     RFC itself for full legal notices.  ";

  revision 2021-10-15 {
    description
      "Initial revision";
    reference
      "RFC xxxx: Title to be completed";
  }

  container data-collection {
    description
      "Defines the information for each collected object";
    list mdt-subscriptions {
      key "subscription-id";
      description "Contains the list of current subscriptions on the
        local device. Enables the collector to select its own
        subscriptions in the list.";
      leaf subscription-id {
        type uint64;
        description
          "Id of the subscription generated by the telemetry emitter.
           The collector can use this id to retrieve information
           about the collection status for the corresponding paths.

           The type is inspired by openconfig-telemetry. TODO check if
           ietf has telemetry modules that we could leafref to.

           path to subscription id in openconfig:
           openconfig-telemetry:telemetry-system/subscriptions/
            persistent-subscriptions/persistent-subscription/state/oid";
      }
      leaf datastore {
        type ds:datastore-ref;
        description
          "The datastore from which the data for this subscription has 
          been collected.";
      }
      list mdt-path-data-manifest {
        key "path";
        description
          "Status of the collection for the given path";
        leaf path {
          type string;
          description
            "The path that was configured to collect information
             about this object. Sensor path syntax is
               module_name:node_name ( / (module_name:)? node_name)*
             where module_name is the name of a module and node_name is
             the name of a node (list, container or leaf). Module name
             is only necessary if the preceding node in the path is not
             defined in the same module.

             Module name must be defined in /platform/module-set and
             every node name must be defined in the preceding node
             in the path.";
        }
        leaf requested-period {
          type uint64;
          description
            "Requested period, in millisecond, between two successive
            updates.";
          // when on-change is false;
        }
        leaf current-period {
          type uint64;
          description
            "Current period, in millisecond, between two successive
            updates.";
          // when on-change is false;
        }
        leaf on-change {
          type boolean;
          description
            "Whether the path is collected only when there is a
            change, i.e. Event-Driven Telemetry is enabled.";
        }
        leaf suppress-redundancy {
          type boolean;
          description
            "Whether the information is sent at every period or only
            when there is a change between two successive pollings.";
        }
      }
      // we could augment here with other kind of collection items
    }
  }
}
