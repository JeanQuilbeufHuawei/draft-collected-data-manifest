module ietf-collected-data-platform-manifest {
  yang-version 1.1;
  namespace "urn:ietf:params:xml:ns:yang:ietf-collected-data-platform-manifest";
  prefix platform-manifest;

  import ietf-yang-library {
    prefix yanglib;
    reference "RFC8525: YANG Library";
  }

  import ietf-yang-packages {
    prefix pkgs;
    reference "RFC  XXXX: YANG Packages.";
  }

  organization
    "IETF NETCONF (Network Configuration) Working Group";
  contact
    "WG Web:   <https://datatracker.ietf.org/wg/netconf/>
     WG List:  <mailto:netconf@ietf.org>
     Author:   Benoit Claise  <mailto:benoit.claise@huawei.com>
     Author:   Jean Quilbeuf   <mailto:jean.quilbeuf@huawei.com>";
  description
    "This module describes the platform information to be used as
     context of data collection from a given network element. The
     contents of this model must be streamed along with the data
     streamed from the network element so that the platform context
     of the data collection can be retrieved later.

     The data content of this model should not change except on
     upgrade or patching of the device.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2022 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).
     This version of this YANG module is part of RFC XXXX; see the
     RFC itself for full legal notices.  ";

  revision 2021-10-15 {
    description
      "Initial revision";
    reference
      "RFC xxxx: Title to be completed";
  }

  container platform {
    description
      "Contains information about the platform that allows to identify
       and understand the individual data collection information.  ";
    leaf platform {
      type string;
      description
        "Platform on which this module is implemented.";
    }
    leaf software-version {
      type string;
      description
        "Name of the version of software. With respect to most network
         device appliances, this will be the operating system version.
         But for other YANG module implementation, this would be a
         version of appliance software. Ultimately, this should
         correspond to a version string that will be recognizable by the
         consumers of the platform.";
    }
    leaf software-flavor {
      type string;
      description
        "A variation of a specific version where YANG model support
         may be different.  Depending on the vendor, this could be a
         license, additional software component, or a feature set.";
    }
    leaf os-version {
      type string;
      description
        "Version of the operating system using this module. This is
         primarily useful if the software implementing the module is an
         application that requires a specific operating system
         version.";
    }
    leaf os-type {
      type string;
      description
        "Type of the operating system using this module. This is
         primarily useful if the software implementing the module is an
         application that requires a specific operating system type.";
    }
    container yang-library {
      description
        "The YANG library of the device specifying the modules available
        in each of the datastores.";
      uses yanglib:yang-library-parameters;
    }
    container packages-set{
      description
        "Alternatively to module-set, use a list of yang packages to
         describe the list of available schema on the platform";
      uses pkgs:yang-ds-pkg-ref;
    }
  }
}
