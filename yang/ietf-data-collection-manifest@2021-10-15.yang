module ietf-data-collection-manifest {
  yang-version 1.1;
  namespace "urn:ietf:params:xml:ns:yang:ietf-data-collection-manifest";
  prefix data-manifest;

  /*import ietf-datastores {
    prefix ds;
    reference "RFC 8342: Network Management Datastore Architecture.";
  }*/

  import ietf-inet-types {
    prefix inet;
    reference
      "RFC 6991: Common YANG Data Types";
  }

  import ietf-interfaces {
    prefix if;
    reference
      "RFC 8343: A YANG Data Model for Interface Management";
  }

  import ietf-network-instance {
    prefix ni;
    reference
      "RFC 8529: YANG Data Model for Network Instances";
  }

  import ietf-platform-manifest {
    prefix p-mf;
    reference "RFC XXXX: Title to be completed";
  }

  import ietf-subscribed-notifications {
    prefix sn;
    reference "RFC 8639: A YANG Data Model for Subscriptions to
                 Event Notifications";
  }

  import ietf-yang-push {
    prefix yp;
    reference "RFC 8641: Subscriptions to YANG Datastores";
  }

  organization
    "IETF OPSAWG (Network Configuration) Working Group";
  contact
    "WG Web:   <https://datatracker.ietf.org/wg/opsawg/>
     WG List:  <mailto:opsawg@ietf.org>
     Author:   Benoit Claise  <mailto:benoit.claise@huawei.com>
     Author:   Jean Quilbeuf   <mailto:jean.quilbeuf@huawei.com>";
  description
    "This module describes the context of data collection from a
     given network element. The contents of this model must be
     streamed along with the data streamed from the network
     element so that the context of the data collection can
     be retrieved later.

     This module must be completed with
     ietf-platform-manifest
     to capture the whole context of a data collection session.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.  ";

  revision 2021-10-15 {
    description
      "Initial revision";
    reference
      "RFC xxxx: Title to be completed";
  }

  container data-collections {
    config false;
    description
      "Contains the configuration and statistics for the collected data,
      per node in the network.";
    list data-collection {
    key platform-id;
    description
      "Defines the information for each collected object";
      leaf platform-id {
        type leafref {
            path "/p-mf:platforms/p-mf:platform/p-mf:id";
        }
        description
          "Id of the platform collecting the data. This id is the same
          as the one in the platform manifest.";
      }
      container yang-push-subscriptions {
        /*
         * Copy-pasting here some of the contents of the "subscriptions"
         * container from ietf-subscribed notification. We need
         * a cleaner way to do this (i.e. a design-time schema-mount
         * including augmenting modules).
         */
        description
          "Contains the list of currently active subscriptions, i.e.,
           subscriptions that are currently in effect, used for
           subscription management and monitoring purposes.  This
           includes subscriptions that have been set up via
           RPC primitives as well as subscriptions that have been
           established via configuration.";
        list subscription {
          key "id";
          description
            "The identity and specific parameters of a subscription.
             Subscriptions in this list can be created using a control
             channel or RPC or can be established through configuration.

             If the 'kill-subscription' RPC or configuration operations
             are used to delete a subscription, a
             'subscription-terminated' message is sent to any active or
             suspended receivers.";
          leaf id {
            type sn:subscription-id;
            description
              "Identifier of a subscription; unique in a given
               publisher.";
          }
          uses sn:subscription-policy {
            refine "target/stream/stream" {
              description
                "Indicates the event stream to be considered for this
                 subscription.  If an event stream has been removed
                 and can no longer be referenced by an active
                 subscription, send a 'subscription-terminated'
                 notification with 'stream-unavailable' as the reason.
                 If a configured subscription refers to a nonexistent
                 event stream, move that subscription to the
                 'invalid' state.";
            }
            refine "transport" {
              description
                "For a configured subscription, this leaf specifies the
                 transport used to deliver messages destined for all
                 receivers of that subscription.  This object is
                 mandatory for subscriptions in the configuration
                 datastore.  This object (1) is not mandatory for dynamic
                 subscriptions in the operational state datastore and
                 (2) should not be present for other types of dynamic
                 subscriptions.";
            }
          }
          choice notification-message-origin {
            if-feature "sn:configured";
            description
              "Identifies the egress interface on the publisher
               from which notification messages are to be sent.";
            case interface-originated {
              description
                "When notification messages are to egress a specific,
                 designated interface on the publisher.";
              leaf source-interface {
                if-feature "sn:interface-designation";
                type if:interface-ref;
                description
                  "References the interface for notification messages.";
              }
            }
            case address-originated {
              description
                "When notification messages are to depart from a
                 publisher using a specific originating address and/or
                 routing context information.";
              leaf source-vrf {
                if-feature "sn:supports-vrf";
                type leafref {
                  path "/ni:network-instances/ni:network-instance/ni:name";
                }
                description
                  "VRF from which notification messages should egress a
                   publisher.";
              }
              leaf source-address {
                type inet:ip-address-no-zone;
                description
                  "The source address for the notification messages.
                   If a source VRF exists but this object doesn't, a
                   publisher's default address for that VRF must
                   be used.";
              }
            }
          }
          leaf configured-subscription-state {
            if-feature "sn:configured";
            type enumeration {
              enum valid {
                value 1;
                description
                  "The subscription is supportable with its current
                   parameters.";
              }
              enum invalid {
                value 2;
                description
                  "The subscription as a whole is unsupportable with its
                   current parameters.";
              }
              enum concluded {
                value 3;
                description
                  "A subscription is inactive, as it has hit a
                   stop time.  It no longer has receivers in the
                   'active' or 'suspended' state, but the subscription
                   has not yet been removed from configuration.";
              }
            }
            config false;
            description
              "The presence of this leaf indicates that the subscription
               originated from configuration, not through a control
               channel or RPC.  The value indicates the state of the
               subscription as established by the publisher.";
          }
        }
      }
      // we could augment here with other kind of collection items
    }
  }


/*
 *  Copy pasting here the augments from ietf-yang-push as we need
 *  them for the subscription information.
 */


  augment "/data-collections/data-collection/yang-push-subscriptions/subscription" {
    //when 'yp:datastore';
    description
      "This augmentation adds objects to a subscription that are
       specific to a datastore subscription, i.e., a subscription to
       a stream of datastore node updates.";
    uses yp:update-policy;
  }

}
