module ietf-platform-manifest {
  yang-version 1.1;
  namespace "urn:ietf:params:xml:ns:yang:ietf-platform-manifest";
  prefix p-mf;

  import ietf-yang-schema-mount {
    prefix yangmnt;
    reference
      "RFC8528: YANG Schema Mount";
  }

  organization
    "IETF OPSAWG (Operations and Management Area) Working Group";
  contact
    "WG Web:   <https://datatracker.ietf.org/wg/opsawg/>
     WG List:  <mailto:opsawg@ietf.org>
     Author:   Benoit Claise   <mailto:benoit.claise@huawei.com>
     Author:   Jean Quilbeuf   <mailto:jean.quilbeuf@huawei.com>
     Author:   Diego R. Lopez  <diego.r.lopez@telefonica.com>
     Author:   Ignacio Dominguez
                          <ignacio.dominguezmartinez@telefonica.com>
     Author:   Thomas Graf     <thomas.graf@swisscom.com>";
  description
    "This module describes the platform information to be used as
     context of data collection from a given network element. The
     contents of this model must be streamed along with the data
     streamed from the network element so that the platform context
     of the data collection can be retrieved later.

     The data content of this model should not change except on
     upgrade or patching of the device.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.  ";

  revision 2025-02-21 {
    description
      "Initial revision";
    reference
      "RFC xxxx: A Data Manifest for Contextualized Telemetry Data";
  }

  grouping platform-details {
    description
        "This grouping contains the information about a particular
        platform, as stored in the YANG catalog.";
    leaf name {
      type string{
          length "1..1023";
        }
      description
        "Model of the platform from which data is collected.";
    }
    leaf vendor {
      type string {
          length "1..1023";
        }
      description
        "Organization that implements that platform.";
    }
    leaf vendor-pen {
  	type uint32;
  	description "Vendor's registered Private Enterprise Number";
    reference
        "RFC9371: Registration Procedures for Private Enterprise
        Numbers (PENs)";
    }
    leaf software-version {
      type string {
          length "1..1023";
        }
      description
        "Name of the version of software. With respect to most
        network device appliances, this will be the operating system
        version. But for other YANG module implementation, this
        would be a version of appliance software. Ultimately, this
        should correspond to a version string that will be
        recognizable by the consumers of the platform.";
    }
    leaf software-flavor {
      type string {
          length "1..1023";
        }
      description
        "A variation of a specific version where YANG model support
         may be different.  Depending on the vendor, this could be a
         license, additional software component, or a feature set.";
    }
    leaf os-version {
      type string {
          length "1..1023";
        }
      description
        "Version of the operating system using this module. This is
         primarily useful if the software implementing the module is
         an application that requires a specific operating system
         version.";
    }
    leaf os-type {
      type string {
          length "1..1023";
        }
      description
        "Type of the operating system using this module. This is
         primarily useful if the software implementing the module is
         an application that requires a specific operating system
         type.";
    }
  }

  container platforms{
    config false;
    description
      "Top container including all platforms in scope. If this model
      is hosted on a single device, it should contain a single entry
      in the list. At the network level, it should contain an entry
      for every monitored platform.";
    list platform {
      key id;
      description
        "Contains information about the platform that allows
        identifying and understanding the individual data collection
        information.";
      leaf id {
        type string {
          length "1..1023";
        }
        description
          "Identifies a given platform on the network, for instance
          the 'sysName' of the platform. The 'id' has to be unique
          within the network scope.";
      }
      uses platform-details;
      yangmnt:mount-point yang-library;
    }
  }
}
