module ietf-data-collection-manifest {
  yang-version 1.1;
  namespace "urn:ietf:params:xml:ns:yang:ietf-data-collection-manifest";
  prefix d-mf;

  import ietf-platform-manifest {
    prefix p-mf;
    reference "RFC XXXX: Title to be completed";
  }

  import ietf-subscribed-notifications {
    prefix sn;
    reference "RFC 8639: A YANG Data Model for Subscriptions to
                 Event Notifications";
  }

  import ietf-yang-push-modif {
    prefix yp;
    reference "RFC 8641: Subscriptions to YANG Datastores. TODO fix and
    used original version. This import is a modified version so that
    it compiles.";
  }

  import ietf-yang-types {
    prefix yang;
    reference
      "RFC 6991: Common YANG Data Types";
  }

  organization
    "IETF OPSAWG (Network Configuration) Working Group";
  contact
    "WG Web:   <https://datatracker.ietf.org/wg/opsawg/>
     WG List:  <mailto:opsawg@ietf.org>
     Author:   Benoit Claise   <mailto:benoit.claise@huawei.com>
     Author:   Jean Quilbeuf   <mailto:jean.quilbeuf@huawei.com>
     Author:   Diego R. Lopez  <diego.r.lopez@telefonica.com>
     Author:   Ignacio Dominguez
                          <ignacio.dominguezmartinez@telefonica.com>
     Author:   Thomas Graf     <thomas.graf@swisscom.com>";
  description
    "This module describes the context of data collection from a
     given network element. The contents of this model must be
     streamed along with the data streamed from the network
     element so that the context of the data collection can
     be retrieved later.

     This module must be completed with
     ietf-platform-manifest
     to capture the whole context of a data collection session.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2022 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.  ";

  revision 2023-03-08 {
    description
      "Initial revision";
    reference
      "RFC xxxx: Title to be completed";
  }

  container data-collections {
    config false;
    description
      "Contains the configuration and statistics for the collected data,
      per node in the network.";
    list data-collection {
    key platform-id;
    description
      "Defines the information for each collected object";
      leaf platform-id {
        type leafref {
            path "/p-mf:platforms/p-mf:platform/p-mf:id";
        }
        description
          "Id of the platform collecting the data. This id is the same
          as the one in the platform manifest.";
      }
      container yang-push-subscriptions {
        /*
         * Copy-pasting here some of the contents of the "subscriptions"
         * container from ietf-subscribed notification.
         */
        description
          "Contains the list of currently active subscriptions, i.e.,
           subscriptions that are currently in effect, used for
           subscription management and monitoring purposes.  This
           includes subscriptions that have been set up via
           RPC primitives as well as subscriptions that have been
           established via configuration.";
        list subscription {
          key "id";
          description
            "The identity and specific parameters of a subscription.
             Subscriptions in this list can be created using a control
             channel or RPC or can be established through configuration.

             If the 'kill-subscription' RPC or configuration operations
             are used to delete a subscription, a
             'subscription-terminated' message is sent to any active or
             suspended receivers.";
          leaf id {
            type sn:subscription-id;
            description
              "Identifier of a subscription; unique in a given
               publisher.";
          }
          choice target {
            mandatory true;
            description
              "Identifies the source of information against which a
               subscription is being applied as well as specifics on the
               subset of information desired from that source.";
            case stream {
                description
                  "An event stream filter can be applied to a
                  subscription. That filter should always be fully
                  included in the Data Collection manifest, i.e. common
                  filters need to be added here.";
                leaf stream {
                  type leafref {
                    path "/p-mf:platforms/p-mf:platform[p-mf:id=current()/../../../platform-id]/p-mf:yang-push-streams/p-mf:stream/p-mf:name";
                  }
                  mandatory true;
                  description
                    "Indicates the event stream to be considered for
                     this subscription.";
                }
                uses sn:stream-filter-elements;
            }
            case datastore {
                description
                  "Yang-push subscription from a datastore.
                   That filter should always be fully included in the
                   Data Collection manifest, i.e. common filters need
                   to be added here.";
               leaf datastore {
                 type leafref {
                   path "/p-mf:platforms/p-mf:platform[p-mf:id=current()/../../../platform-id]/p-mf:yang-library/p-mf:datastore/p-mf:name";
                 }
                 mandatory true;
                 description
                   "Datastore from which to retrieve data.";
               }
               uses yp:selection-filter-types;
            }
          }
          leaf transport {
            type sn:transport;
            description
              "For a configured subscription, this leaf specifies the
               transport used to deliver messages destined for all
               receivers of that subscription.";
          }
          leaf encoding {
            type sn:encoding;
            description
              "The type of encoding for notification messages.  For a
               dynamic subscription, if not included as part of an
               'establish-subscription' RPC, the encoding will be
               populated with the encoding used by that RPC.  For a
               configured subscription, if not explicitly configured,
               the encoding will be the default encoding for an
               underlying transport.";
          }
          leaf purpose {
            type string;
            description
              "Open text allowing a configuring entity to embed the
               originator or other specifics of this subscription.";
          }
          uses sn:update-qos;
          uses yp:update-policy-modifiable;
          leaf current-period {
            when '../periodic';
            type yp:centiseconds;
            description
              "Period during two succesive data collections, in the
              current state. Might differ from the configured period
              when the plaftorm might increase the period
              automatically when it is overloaded.";
          }
          container receivers {
            description
              "Set of receivers in a subscription.";
            list receiver {
              key "name";
              min-elements 1;
              description
                "A host intended as a recipient for the notification
                 messages of a subscription.  For configured
                 subscriptions, transport-specific network parameters
                 (or a leafref to those parameters) may be augmented to
                 a specific receiver in this list.";
              leaf name {
                type string;
                description
                  "Identifies a unique receiver for a subscription.";
              }
              leaf sent-event-records {
                type yang:zero-based-counter64;
                config false;
                description
                  "The number of event records sent to the receiver.
                  The count is initialized when a dynamic subscription
                  is established or when a configured receiver
                   transitions to the 'valid' state.";
              }
              leaf excluded-event-records {
                type yang:zero-based-counter64;
                config false;
                description
                  "The number of event records explicitly removed via
                   either an event stream filter or an access control
                   filter so that they are not passed to a receiver.
                   This count is set to zero each time
                   'sent-event-records' is initialized.";
              }
              leaf state {
                type enumeration {
                  enum active {
                    value 1;
                    description
                      "The receiver is currently being sent any
                       applicable notification messages for the
                       subscription.";
                  }
                  enum suspended {
                    value 2;
                    description
                      "The receiver state is 'suspended', so the
                       publisher is currently unable to provide
                       notification messages for the subscription.";
                  }
                  enum connecting {
                    value 3;
                    description
                      "A subscription has been configured, but a
                       'subscription-started' subscription state change
                       notification needs to be successfully received
                       before notification messages are sent. ";
                  }
                  enum disconnected {
                    value 4;
                    description
                      "A subscription has failed to send a
                       'subscription-started' state change to the
                       receiver.  Additional connection attempts are not
                       currently being made.";
                  }
                }
                config false;
                mandatory true;
                description
                  "Specifies the state of a subscription from the
                   perspective of a particular receiver.  With this
                   information, it is possible to determine whether a
                   publisher is currently generating notification
                   messages intended for that receiver.";
              }
            }
          }
        }
      }
      // we could augment here with other kind of collection items
    }
  }
}
