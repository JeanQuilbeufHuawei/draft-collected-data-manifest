module ietf-data-collection-manifest {
  yang-version 1.1;
  namespace "urn:ietf:params:xml:ns:yang:ietf-data-collection-manifest";
  prefix d-mf;

  import ietf-platform-manifest {
    prefix p-mf;
    reference "RFC XXXX: Title to be completed";
  }
  import ietf-yang-schema-mount {
    prefix yangmnt;
    reference
      "RFC8528: YANG Schema Mount";
  }

  organization
    "IETF OPSAWG (Operations and Management Area) Working Group";
  contact
    "WG Web:   <https://datatracker.ietf.org/wg/opsawg/>
     WG List:  <mailto:opsawg@ietf.org>
     Author:   Benoit Claise   <mailto:benoit.claise@huawei.com>
     Author:   Jean Quilbeuf   <mailto:jean.quilbeuf@huawei.com>
     Author:   Diego R. Lopez  <diego.r.lopez@telefonica.com>
     Author:   Ignacio Dominguez
                          <ignacio.dominguezmartinez@telefonica.com>
     Author:   Thomas Graf     <thomas.graf@swisscom.com>";
  description
    "This module describes the context of data collection from a
     given network element. The contents of this model must be
     streamed along with the data streamed from the network
     element so that the context of the data collection can
     be retrieved later.

     This module must be completed with
     ietf-platform-manifest
     to capture the whole context of a data collection session.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.

     Copyright (c) 2025 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).
     This version of this YANG module is part of RFC XXXX; see the
     RFC itself for full legal notices.  ";

  revision 2024-07-02 {
    description
      "Initial revision";
    reference
      "RFC xxxx: A Data Manifest for Contextualized Telemetry Data";
  }

  container data-collections {
    config false;
    description
      "Contains the configuration and statistics for the collected data,
      per node in the network.";
    list data-collection {
    key platform-id;
    description
      "Defines the information for each collected object";
      leaf platform-id {
        type leafref {
            path "/p-mf:platforms/p-mf:platform/p-mf:id";
        }
        description
          "Identifier of the platform collecting the data. This
          identifier is the same as the one in the platform
          manifest.";
      }
      yangmnt:mount-point yang-push-collection;
    }
  }
}
