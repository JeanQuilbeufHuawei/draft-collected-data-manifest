module ietf-data-collection-manifest-statistics {
  yang-version 1.1;
  namespace "urn:ietf:params:xml:ns:yang:ietf-data-collection-statistics";
  prefix dcs;

  import ietf-subscribed-notifications {
    prefix sn;
    reference "RFC 8639: A YANG Data Model for Subscriptions to
    Event Notifications";
  }

  import ietf-yang-push {
    prefix yp;
    reference "RFC 8641: Subscriptions to YANG Datastores.";
  }

  organization
    "IETF OPSAWG (Network Configuration) Working Group";
  contact
    "WG Web:   <https://datatracker.ietf.org/wg/opsawg/>
    WG List:  <mailto:opsawg@ietf.org>
    Author:   Benoit Claise   <mailto:benoit.claise@huawei.com>
    Author:   Jean Quilbeuf   <mailto:jean.quilbeuf@huawei.com>
    Author:   Diego R. Lopez  <diego.r.lopez@telefonica.com>
    Author:   Ignacio Dominguez
    <ignacio.dominguezmartinez@telefonica.com>
    Author:   Thomas Graf     <thomas.graf@swisscom.com>";
  description
    "This module augments subscribed notification with the
    current-period statistics reporting the actual collection
    period.

    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.

    Copyright (c) 2022 IETF Trust and the persons identified as
    authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).
    This version of this YANG module is part of RFC XXXX; see the
    RFC itself for full legal notices.  ";

  revision 2024-07-02 {
    description
      "Initial revision";
    reference
      "RFC xxxx: Title to be completed";
  }

  augment "/sn:subscriptions/sn:subscription" {
    description
        "Add extra statistics about data collection";

    leaf current-period {
      when '../yp:periodic';
      type yp:centiseconds;
      description
        "Period during two succesive data collections, in the
        current state. Might differ from the configured period
        when the plaftorm might increase the period
        automatically when it is overloaded.";
    }
  }
}
